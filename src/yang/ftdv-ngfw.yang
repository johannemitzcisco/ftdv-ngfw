module ftdv-ngfw {

  namespace "http://example.com/ftdv-ngfw";
  prefix ftdv-ngfw;

  import ietf-inet-types { prefix inet; }
  import tailf-common { prefix tailf; }
  import tailf-ncs { prefix ncs; }
  import tailf-kicker { prefix kicker; }
//  import cisco-etsi-nfvo { prefix nfvo; }
  import etsi-nfv-descriptors { prefix nfv; }
  import network { prefix network; }
  
  description
    "VNF deployment service for VMWare using Cisco NFVO package";

  revision 2020-03-24 {
    description
      "Modified ip addressing to use pools only";
  }
  revision 2019-03-12 {
    description
      "Initial revision.";
  }

  identity ip-addressing {
    base ncs:plan-state;
  }
  identity vnfs-initialized {
    base ncs:plan-state;
  }
  identity vnfs-deployed {
    base ncs:plan-state;
  }
  identity vnfs-api-available {
    base ncs:plan-state;
  }
  identity vnfs-registered-with-manager {
    base ncs:plan-state;
  }
  identity vnfs-registered-with-nso {
    base ncs:plan-state;
  }
  identity vnfs-synchronized-with-nso {
    base ncs:plan-state;
  }
  identity vnfs-synchronized-with-manager {
    base ncs:plan-state;
  }
  identity load-balancing-configured {
    base ncs:plan-state;
  }
  identity vnfs-configured {
    base ncs:plan-state;
  }
  identity vnfs-configurations-deployed {
    base ncs:plan-state;
  }
  identity scaling-monitoring-enabled {
    base ncs:plan-state;
  }

  identity vnf {
    base ncs:plan-component-type;
  }
  identity deployed {
    base ncs:plan-state;
  }
  identity api-available {
    base ncs:plan-state;
  }
  identity initialized {
    base ncs:plan-state;
  }
  identity registered-with-nso {
    base ncs:plan-state;
  }
  identity registered-with-manager {
    base ncs:plan-state;
  }
  identity synchronized-with-nso {
    base ncs:plan-state;
  }
  identity synchronized-with-manager {
    base ncs:plan-state;
  }
  identity configurable {
    base ncs:plan-state;
  }
  identity configured {
    base ncs:plan-state;
  }

  grouping access-rule-grouping {
    list access-rule {
      key name;
      leaf name {
        type string;
      }
      leaf source-zone {
        type string;
//        tailf:non-strict-leafref {
//          path "../../state/zone/name";
//        }
      }
      leaf source-port {
        type string;
//        tailf:non-strict-leafref {
//          path "../../state/port/name";
//        }
      }
      leaf action {
        type enumeration {
          enum "PERMIT";
          enum "TRUST";
          enum "DENY";
        }
      }
    }
  }

  grouping state-grouping {
    container state {
      config "false";
      list zone {
        key name;
        leaf name {
          type string;
        }
        leaf id {
          type string;
        }
      }
      list port {
        key name;
        leaf name {
          type string;
        }
        leaf id {
          type string;
        }
      }
      list user {
        key name;
        leaf name {
          type string;
        }
        leaf id {
          type string;
        }
      }
    }
  }

  grouping manager-action-grouping {
    tailf:action sync-manager-with-nso {
      tailf:actionpoint ftdv-ngfw-syncManagerWithNso-action;
      input {}
      output {
        leaf result {
          type string;
        }
      }
    }
    tailf:action deploy-manager-configurations {
      tailf:actionpoint ftdv-ngfw-deployManagerConfigurations-action;
      input {}
      output {
        leaf result {
          type string;
        }
      }
    }
  }

  grouping device-action-grouping {
    tailf:action provision-ftd-device {
      tailf:actionpoint ftdv-ngfw-provisionFTDDevice-action;
      input {}
      output {
        leaf result {
          type string;
        }
      }
    }
    tailf:action configure {
      tailf:actionpoint ftdv-ngfw-configureDevice-action;
      input {}
      output {
        leaf result {
          type string;
        }
      }
    }
    tailf:action sync-vnf-with-nso {
      tailf:actionpoint ftdv-ngfw-syncVnfWithNso-action;
      input {}
      output {
        leaf result {
          type string;
        }
      }
    }
    tailf:action deregister-vnf-with-nso {
      tailf:actionpoint ftdv-ngfw-deregisterVnfWithNso-action;
      input {}
      output {
        leaf result {
          type string;
        }
      }
    }
    tailf:action register-vnf-with-nso {
      tailf:actionpoint ftdv-ngfw-registerVnfWithNso-action;
      input {}
      output {
        leaf result {
          type string;
        }
      }
    }
    tailf:action get-device-data {
      tailf:actionpoint ftdv-ngfw-getDeviceData-action;
      input {}
      output {
        leaf result {
          type string;
        }
      }
    }
    tailf:action add-user {
      tailf:actionpoint ftdv-ngfw-addUser-action;
      input {
        leaf username {
          mandatory "true";
          type string;
        }
        leaf password {
          mandatory "true";
          type string;
        }
      }
      output {
        leaf result {
          type string;
        }
      }
    }
    tailf:action delete-user {
      tailf:actionpoint ftdv-ngfw-deleteUser-action;
      input {
        leaf username {
          tailf:info "Name of user to delete (if no user available run get-device-data action)";
          mandatory "true";
          type leafref {
            path "../../state/user/name";
          }
        }
      }
      output {
        leaf result {
          type string;
        }
      }
    }
  }

  grouping vnf-deployment-grouping {
    leaf tenant {
      tailf:info "Tenant of this site and owner of the VNF";
      type leafref {
        path "/ftdv-ngfw:vnf-manager/ftdv-ngfw:site/ftdv-ngfw:tenant";
      }
    }
    leaf deployment-name {
      tailf:info "Unique deployment/service id";
      tailf:cli-allow-range;
      type string;
    }
    container manager {
      leaf name {
        type leafref {
          path "../../../managers/manager/name";
        }
      }
      uses manager-action-grouping {
        when "name";
      }
    }
    container networks {
      list network {
        key name;
        leaf name {
// TODO: Need to put in a check that vnf-catalog item being used
//       has all its networks represented here as the vnf-deployment.xml
//       is expecting it
          type leafref {
            path "../../../../networks/network/name";
          }
        }
        leaf catalog-descriptor-vdu-id {
          type leafref {
              path "/nfv:nfv/nfv:vnfd/nfv:vdu/nfv:int-cpd/nfv:id";
          }
//            must "/nfv:nfv/nfv:vnfd[nfv:id=deref(../../../catalog-vnf/../descriptor-name]/nfv:vdu[nfv:id=deref(../../../catalog-vnf/../descriptor-vdu]/nfv:int-cpd/nfv:id" {
//              tailf:dependency "/nfv:nfv/nfv:vnfd/nfv:vdu/nfv:int-cpd";
//            }
        }
        container ftd-interface {
          choice ftd-interface {
            case inside {
              leaf inside {
                type empty;
              }
            }
            case outside {
              leaf outside {
                type empty;
              }
            }
          }
        }
        leaf-list ftd-route-network {
          type leafref {
            path  "../../../../networks/network/name";
          }
          must "deref(.)/../ftd-network" {
            tailf:dependency "/vnf-manager/site/networks/network";
          }
        }
      }
    }
    list deployment {
      key vnf-catalog-name;
      leaf vnf-catalog-name {
        type leafref {
          path "/ftdv-ngfw:vnf-manager/ftdv-ngfw:vnf-catalog/ftdv-ngfw:name";
        }
      }
      leaf order {
        type uint16;
        default 1;
      }
      must "((../scaling/type != 'vcpu-static' and count(.) = 1) or
             (../scaling/type = 'vcpu-static' and count(.) > 0))";
      list resource-pool-allocation {
        config "false";
        key network;
        leaf network {
          type string;
        }
        leaf name {
          type string;
        }
      }
      container scaling {
        container threshold {
          leaf scale-up {
            when "../../../../scaling/type != 'none'";
            tailf:info "Threshold to signal addition VNFs/larger sized VNF are/is needed";
            type int64;
          }
          leaf scale-down {
            when "../../../../scaling/type != 'none'";
            tailf:info "Threshold to signal that VNFs can be decommissioned or smaller sized VNF should be used";
            type int64;
          }
        }
        leaf status {
          config "false";
          type enumeration {
            enum "inactive";
            enum "active";
          }
          default "inactive";
        }
      }
    }
    container scaling {
      tailf:info "Scaling attributes";
      leaf type {
        mandatory "true";
        type enumeration {
          enum "none";
          enum "horizontal";
          enum "vcpu-static";
        }
      }
      container load-balance {
        choice load-balancer {
        }
        leaf status {
          config "false";
          type enumeration {
            enum "Unknown";
            enum "Initialized";
            enum "Enabled";
            enum "Disabled";
            enum "Failure";
          }
          default "Unknown";
        }
      }
    }
    leaf status {
      tailf:info "Status of the Deployment (inclusive of all VNFs)";
      //config "false";
      type enumeration {
        enum "Unknown";
        enum "Initializing";
        enum "Deploying";
        enum "Starting VNFs";
        enum "Registering";
        enum "Provisioning";
        enum "Provisioned";
        enum "Synchronizing";
        enum "Synchronized";
        enum "Configurable";
        enum "ConfiguredStage1";
        enum "ConfiguredStage2";
        enum "Configured";
        enum "ConfigurationsDeployed";
        enum "Operational";
        enum "Failure";
      }
      default "Unknown";
    }
    leaf status-message {
      config "false";
      type string;
    }
    list device {
      tailf:info "Information about devices in the Deployment";
      config "false";
      key name;
      leaf name {
        type string;
      }
      leaf vm-name {
        type string;
      }
      leaf vmid {
        type string;
      }
      container networks {
        list network {
          key name;
          leaf name {
            type string;
          }
          leaf ip-address {
            type inet:ipv4-address;
          }
          leaf management {
            type empty;
          }
        }
      }
      leaf vnf_catalog {
        config "false";
        type string;
      }
      leaf status {
        tailf:info "Status of the Deployment";
        //config "false";
        type enumeration {
          enum "Unknown";
          enum "Deploying";
          enum "Starting";
          enum "Registering";
          enum "Provisioning";
          enum "Provisioned";
          enum "Registered";
          enum "Synchronizing";
          enum "Synchronized";
          enum "Configurable";
          enum "Configured-Stage-1";
          enum "Configured";
          enum "Operational";
          enum "Failure";
        }
        default "Unknown";
      }
      leaf status-message {
        config "false";
        type string;
      }
      uses device-action-grouping;
      uses state-grouping;
    }
  }

  container vnf-manager {
    list site {
      tailf:info "VNF Deployment Site";
      key name;
      leaf name {
        tailf:info "Name of the Site";
        type string;
      }
      leaf-list tenant {
        tailf:info "Tenant of the site";
        type string;
      }
      leaf datacenter-name {
        tailf:info "VMWare datacenter name";
        type string;
        mandatory "true";
      }
      leaf cluster-name {
        tailf:info "VMWare compute cluster name";
        type string;
        mandatory "true";
      }
      leaf datastore-name {
        tailf:info "VMWare datastore name";
        type string;
        mandatory "true";
      }
      container networks {
        list network {
          key name;
          uses network:network-grouping {
            refine name {
              description "Name of the NFVO VNFD external connection point";
            }
            refine resource-pool/name {
              config "false";
            }
          }
          leaf management {
            type empty;
          }
          leaf VMware-name {
            tailf:info "VMware network name";
            type string;
          }
          leaf VMware-switch {
            tailf:info "VMware network name";
            type string;
          }
          leaf ftd-network {
            type empty;
          }
        }
      }
      leaf elastic-services-controller {
        tailf:info "ESC devices that manages this site";
        type leafref {
          path "/ncs:devices/ncs:device/ncs:name";
        }
  //      must "deref(.)/../module[name='esc']" {
  //      must "deref(.)/../module/name ='esc'" {
  //        tailf:dependency "/ncs:devices/ncs:device/ncs:name";
  //      }
        mandatory "true";
      }
      container managers {
        list manager {
          key name;
          leaf name {
            type leafref {
              path "/ncs:devices/ncs:device/ncs:name";
            }
          }
        }
      }

      list vnf-deployment {
        description "Service to stand up scalable FTDv using NFVO Service Pack";
        tailf:info "Service to stand up scalable FTDv using NFVO Service Pack";

        uses ncs:plan-data;
        uses ncs:service-progress-monitoring-data;
        uses ncs:service-data;
        ncs:servicepoint ftdv-ngfw-scalable-servicepoint;

        key "tenant deployment-name";
        uses vnf-deployment-grouping;
      }
    }
    tailf:action handle-esc-notifications {
      tailf:actionpoint ftdv-ngfw-handle-esc-notifications;
      input {
        uses kicker:action-input-params;
      }
      output {}
    }

    container devices {
      config "false";
      list device {
        key vm_name;
        leaf vm_name {
          type string;
        }
        leaf site {
          type string;
        }
        container vnf-deployment {
          leaf tenant {
            type string;
          }
          leaf deployment-name {
            type string;
          }
        }
        leaf event-type {
          type string;
        }
      }
      tailf:action delete-events {
        tailf:actionpoint ftdv-ngfw-delete-device-events;
        input {}
        output {}
      }
    }
    container config {
       description 
         "This container provides a place for other modules that are augmenting
          to place any configuration information that they may require";
    }

    list vnf-catalog {
      key name;
      leaf name {
        tailf:info "Name of the VNF";
        type string;
      }
      leaf descriptor-name {
        tailf:info "Name of the VNFD from nfvo/vnfd";
        type leafref {
          path "/nfv:nfv/nfv:vnfd/nfv:id";
        }
        mandatory "true";
      }
      leaf descriptor-flavor {
        tailf:info "Name of the VNFD flavor";
        type leafref {
          path "deref(../ftdv-ngfw:descriptor-name)/../nfv:df/nfv:id";
        }
        when "../descriptor-name";
        mandatory "true";
      }
      leaf descriptor-instantiation-level {
        tailf:info "Name of the VNFD instantiation level";
        type leafref {
          path "deref(../ftdv-ngfw:descriptor-flavor)/../nfv:instantiation-level/nfv:id";
        }
        when "../descriptor-flavor";
        mandatory "true";
      }
      leaf descriptor-vdu {
        tailf:info "Name of the VNFD virtualisation deployment unit";
        type leafref {
          path "deref(../ftdv-ngfw:descriptor-instantiation-level)/../nfv:vdu-level/nfv:vdu-id";
        }
        when "../descriptor-instantiation-level";
        mandatory "true";
      }
      leaf device-profile {
        tailf:info "profile at /devices/profiles/profile to apply";
        type leafref {
          path "/ncs:devices/ncs:profiles/ncs:profile/ncs:name";
        }
        when "../descriptor-vdu";
        mandatory "true";
      }
      leaf bootup-time {
        tailf:info "Maximum time to wait for VNF to be available";
        type uint32;
        mandatory "true";
      }
      leaf recovery-time {
        tailf:info "Maximum time to wait for VNF to restart";
        type uint32;
        mandatory "true";
      }
      leaf day0_authgroup {
        tailf:info "NSO authgroup to use to connect to the VNF";
        type leafref {
          path "/ncs:devices/ncs:authgroups/ncs:group/ncs:name";
        }
        mandatory "true";
      }
      leaf day1_authgroup {
        tailf:info "NSO authgroup to use to connect to the VNF if neccessary";
        type leafref {
          path "/ncs:devices/ncs:authgroups/ncs:group/ncs:name";
        }
      }
      container templates {
        list template {
          key "name";
          leaf name {
            type string;
            tailf:non-strict-leafref {
              path "/ncs:devices/ncs:template/ncs:name";
            }
          }
          container target {
            choice target {
              case manager {
                leaf manager-type {
                  type enumeration {
                    enum "device-registration";
                    enum "device-post-registration";
                    enum "device-configuration";
                  }
                  default "device-registration";
                }
              }
              case nso-managed-device-vnfm {
                leaf nso-managed-device-vnfm-type {
                  type enumeration {
                    enum "alive";
                    enum "scale";
                  }
                }
              }
              case managed-device-vnfm {
                leaf managed-device-vnfm-type {
                  type enumeration {
                    enum "alive";
                    enum "scale";
                  }
                }
              }
              case device {
                leaf device-type {
                  type enumeration {
                    enum "registration";
                    enum "configuration";
                  }
                  default "configuration";
                }
              }
            }
          }
          leaf stage {
            type enumeration {
              enum "1";
              enum "2";
            }
            when "../target/manager-type = 'device-configuration' or
                  ../target/device-type  = 'configuration'";
          }
        }
      }
    }
  }
/*
  container firewall {
    list ftdv-ngfw-advanced {
      description "Service to stand up a FTDv with automated scaling and load balancing";
      key "site tenant deployment-name";
      leaf site {
        type leafref {
          path "/ftdv-ngfw:vnf-manager/ftdv-ngfw:site/ftdv-ngfw:name";
        }
      }
      uses ncs:plan-data;
      uses ncs:service-progress-monitoring-data;
      uses ncs:service-data;
      ncs:servicepoint ftdv-ngfw-advanced-servicepoint;
      uses vnf-deployment-grouping;
      uses access-rule-grouping;
    }
    list ftdv-ngfw-basic {
      description "Service to stand up a single FTDv using ESC directly";
      key "site deployment-name";
      leaf site {
        type leafref {
          path "/ftdv-ngfw:vnf-manager/ftdv-ngfw:site/ftdv-ngfw:name";
        }
      }
      leaf deployment-name {
        tailf:info "Unique deployment/service id";
        tailf:cli-allow-range;
        type string;
      }
      uses ncs:service-data;
      ncs:servicepoint ftdv-ngfw-servicepoint;
      leaf catalog-vnf {
        tailf:info "VNF from the catalog to deploy";
        type leafref {
          path "/ftdv-ngfw:vnf-manager/ftdv-ngfw:vnf-catalog/ftdv-ngfw:name";
        }
      }
      leaf ip-address {
        type inet:ipv4-address;
      }
      uses device-action-grouping;
      uses state-grouping;
      uses access-rule-grouping;
    }
  }
*/
}
